module sonic-telemetry {
    namespace "http://github.com/Azure/sonic-telemetry";
    prefix stel;
    yang-version 1.1;

    import ietf-inet-types {
        prefix inet;
    }

    organization
        "SONiC";

    contact
        "SONiC";

    description
        "SONiC Telemetry";

    revision 2020-11-15 {
        description
            "Initial revision.";
    }

    container sonic-telemetry {
        container DIALOUT_SENSOR_GROUP{
            list DIALOUT_SENSOR_GROUP_LIST {
                key "sensor_group_id";
                leaf sensor_group_id {
                    type string;
                    description
                      "Name or identifier for the sensor group itself.
                       Will be referenced by other configuration specifying a
                       sensor group";
                }
            }
        }
        container DIALOUT_SENSOR_PATH{
            list DIALOUT_SENSOR_PATH_LIST {
                key "sensor_group_id path";
                leaf sensor_group_id {
                    type leafref {
                      path "../../../DIALOUT_SENSOR_GROUP/DIALOUT_SENSOR_GROUP_LIST/sensor_group_id";
                    }
                    description
                      "Reference to the name or identifier of the
                       sensor grouping";
                }
                leaf path {
                    type string;
                    description
                      "The sensor path is a path to a portion of operational
                       state of interest in the data model";
                }
            }
        } 
        container DIALOUT_DESTINATION_GROUP {   
            list DIALOUT_DESTINATION_GROUP_LIST {
                key "group_id";
                leaf group_id {
                    type string;
                    description
                      "List of destination-groups. Destination groups allow the
                       reuse of common telemetry destinations across the
                       telemetry configuration. An operator references a
                       set of destinations via the configurable
                       destination-group-identifier.
                       A destination group may contain one or more telemetry
                       destinations";
                }
            }
        }
        container DIALOUT_DESTINATION {
            list DIALOUT_DESTINATION_LIST {
                key "group_id destination_address destination_port";
                leaf group_id {
                    type leafref {
                      path "../../../DIALOUT_DESTINATION_GROUP/DIALOUT_DESTINATION_GROUP_LIST/group_id";
                    }
                    description
                      "Reference to the name or identifier of the destination grouping";
                }
                leaf destination_address {
                    type inet:ip-address;
                    description
                      "IP address of the telemetry stream destination";
                }
                leaf destination_port {
                    type uint16;
                    description
                      "Protocol (udp or tcp) port number for the telemetry
                       stream destination";
                }

            }
        } 
        container DIALOUT_PERSISTENT_SUBSCRIPTION {
            list DIALOUT_PERSISTENT_SUBSCRIPTION_LIST {
                key "name";                
                leaf name {
                    type string;
                    description
                      "User configured identifier of the telemetry
                       subscription. This value is used primarily for
                       subscriptions configured locally on the network
                       element.";
                }
                leaf local_source_address {
                    type inet:ip-address;
                    description
                      "The IP address which will be the source of packets from
                       the device to a telemetry collector destination.";
                }
                leaf originated_qos_marking {
                    type uint8 {
                      range "0..63" {
                          error-app-tag invalid-dscp-value;
                          error-message "Invalid DSCP Value.";
                      }
                    }
                    description
                      "DSCP marking of packets generated by the telemetry
                       subsystem on the network device.";
                }
                leaf protocol {
                    type enumeration {
                         enum STREAM_SSH;
                         enum STREAM_GRPC;
                         enum STREAM_JSON_RPC;
                         enum STREAM_THRIFT_RPC;
                         enum STREAM_WEBSOCKET_RPC;
                    }
                    description
                      "Selection of the transport protocol for the telemetry
                       stream.";
                }
                leaf encoding {
                    type enumeration {
                         enum ENC_XML;
                         enum ENC_JSON_IETF;
                         enum ENC_PROTO3;
                    }
                    description
                      "Selection of the specific encoding or RPC framework
                       for telemetry messages to and from the network element.";
                }
            }
        }
        container DIALOUT_SUBSCR_SENSOR_PROFILE {
            list DIALOUT_SUBSCR_SENSOR_PROFILE_LIST {
                key "name sensor_group";
                leaf name {
                    type leafref {
                      path "../../../DIALOUT_PERSISTENT_SUBSCRIPTION/DIALOUT_PERSISTENT_SUBSCRIPTION_LIST/name";
                    }
                    description
                      "Reference to the name or identifier of the persistent subscription"; 
                }
                leaf sensor_group {
                    type leafref {
                      path "../../../DIALOUT_SENSOR_GROUP/DIALOUT_SENSOR_GROUP_LIST/sensor_group_id";
                      }
                    description
                      "Reference to the name or identifier of the
                       sensor grouping";
                }
                leaf sample_interval {
                    type uint64;
                    description
                      "Time in milliseconds between the device's sample of a
                       telemetry data source. For example, setting this to 100
                       would require the local device to collect the telemetry
                       data every 100 milliseconds. There can be latency or jitter
                       in transmitting the data, but the sample must occur at
                       the specified interval.";
                }
                leaf heartbeat_interval {
                    type uint64;
                    description
                      "Maximum time interval in seconds that may pass
                       between updates from a device to a telemetry collector.
                       If this interval expires, but there is no updated data to
                       send (such as if suppress_updates has been configured), the
                       device must send a telemetry message to the collector.";
                }
                leaf suppress_redundant {
                    type boolean;
                    description
                      "Boolean flag to control suppression of redundant
                       telemetry updates to the collector platform. If this flag is
                       set to TRUE, then the collector will only send an update at
                       the configured interval if a subscribed data value has
                       changed. Otherwise, the device will not send an update to
                       the collector until expiration of the heartbeat interval.";
                }
            }
        }
        container DIALOUT_SUBSCR_DESTINATION_GROUP {
            list DIALOUT_SUBSCR_DESTINATION_GROUP_LIST {
               key "name group_id";
               leaf name {
                   type leafref {
                     path "../../../DIALOUT_PERSISTENT_SUBSCRIPTION/DIALOUT_PERSISTENT_SUBSCRIPTION_LIST/name";
                   }
                   description
                      "Reference to the name or identifier of the persistent subscription";
               }  
               leaf group_id {
                   type leafref {
                     path "../../../DIALOUT_DESTINATION_GROUP/DIALOUT_DESTINATION_GROUP_LIST/group_id";
                   }
                   description
                      "Reference to the name or identifier of the destination grouping";                   
               }
            }
        }
    }
}
